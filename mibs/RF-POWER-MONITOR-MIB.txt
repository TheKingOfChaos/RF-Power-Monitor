RF-POWER-MONITOR-MIB DEFINITIONS ::= BEGIN

IMPORTS
    MODULE-IDENTITY, OBJECT-TYPE, NOTIFICATION-TYPE, Counter32, Gauge32, Integer32, TimeTicks, enterprises
        FROM SNMPv2-SMI
    DisplayString
        FROM SNMPv2-TC
    MODULE-COMPLIANCE, OBJECT-GROUP, NOTIFICATION-GROUP
        FROM SNMPv2-CONF;

rfPowerMonitor MODULE-IDENTITY
    LAST-UPDATED "202611070000Z"
    ORGANIZATION "RF-Power-Monitor project"
    CONTACT-INFO
        "https://github.com/TheKingOfChaos/RF-Power-Monitor
         kenneth@tkoc.dk"
    DESCRIPTION
        "Mains power monitor based on a Raspberry Pi Pico with a W5500
         Ethernet module. The agent speaks SNMPv1 and SNMPv2c, and all objects
         are read-only. The standard system group (RFC 1213) is also
         implemented."
    REVISION "202611070000Z"
    DESCRIPTION
        "Added the updateSite group (update site check-ins: last result,
         minutes since the last good check-in, failures in a row)."
    REVISION "202611060000Z"
    DESCRIPTION
        "Added the fwUpdate group (firmware update: running slot, slot
         versions, trial state, last result) and the firmwareUpdateKept
         and firmwareRolledBack notifications (SNMPv1 specific-trap 4
         and 5)."
    REVISION "202611010100Z"
    DESCRIPTION
        "Project renamed RF-Power-Monitor: module RF-UPS-MONITOR-MIB is now
         RF-POWER-MONITOR-MIB and the rfUpsMonitor... names are rfPowerMonitor...
         (same OIDs)."
    REVISION "202611010000Z"
    DESCRIPTION
        "Added mainsPowerAlarm and the mainsPowerLostTooLong notification
         (SNMPv1 specific-trap 3): mains lost for 60 seconds."
    REVISION "202610260000Z"
    DESCRIPTION
        "boardTemperature renamed cpuTemperature (same OID, same value).
         Added ambientTemperature from the TMP1075 on the carrier board."
    REVISION "202610170100Z"
    DESCRIPTION
        "Added boardTemperature (firmware 1.0.0)."
    REVISION "202610170000Z"
    DESCRIPTION
        "Added mainsPowerLost and mainsPowerRestored notifications,
         sent as SNMPv1 traps (enterprise 63050, specific-trap 1 and 2)."
    REVISION "202610160000Z"
    DESCRIPTION
        "Initial version: mains power status, change counter and time
         of the last change."
    ::= { enterprises 63050 }

-- Notifications. Under RFC 3584 these map to SNMPv1 traps with
-- enterprise = rfPowerMonitor and specific-trap = the last sub-identifier.

rfPowerMonitorNotifications OBJECT IDENTIFIER ::= { rfPowerMonitor 0 }

mainsPowerLost NOTIFICATION-TYPE
    OBJECTS     { mainsPowerStatus, mainsPowerChanges, mainsPowerLastChange }
    STATUS      current
    DESCRIPTION
        "Mains power was lost. mainsPowerLastChange is the time of the
         loss; the trap time-stamp has the same value."
    ::= { rfPowerMonitorNotifications 1 }

mainsPowerRestored NOTIFICATION-TYPE
    OBJECTS     { mainsPowerStatus, mainsPowerChanges, mainsPowerLastChange }
    STATUS      current
    DESCRIPTION
        "Mains power was restored."
    ::= { rfPowerMonitorNotifications 2 }

mainsPowerLostTooLong NOTIFICATION-TYPE
    OBJECTS     { mainsPowerStatus, mainsPowerChanges, mainsPowerLastChange,
                  mainsPowerAlarm }
    STATUS      current
    DESCRIPTION
        "Mains power has been lost for 60 seconds: mainsPowerAlarm became
         lostTooLong(1). Sent once per outage; if no trap destination
         exists at that moment, it is sent as soon as one does, unless
         mains returns first. mainsPowerLastChange and the trap
         time-stamp are the time of the loss."
    ::= { rfPowerMonitorNotifications 3 }

firmwareUpdateKept NOTIFICATION-TYPE
    OBJECTS     { fwRunningSlot, fwSlotAVersion, fwSlotBVersion, fwLastResult }
    STATUS      current
    DESCRIPTION
        "A firmware update was confirmed and is kept: the new firmware
         received a valid management request during its trial, and
         fwLastResult is installed(1). Sent once, after the device has
         a trap destination and an address."
    ::= { rfPowerMonitorNotifications 4 }

firmwareRolledBack NOTIFICATION-TYPE
    OBJECTS     { fwRunningSlot, fwSlotAVersion, fwSlotBVersion, fwLastResult }
    STATUS      current
    DESCRIPTION
        "The device went back to the firmware it ran before: a new
         firmware crashed or was not reachable during its trial
         (fwLastResult rolledBackCrash(2) or rolledBackUnreachable(3)),
         or a running slot crashed three times and the other slot took
         over (fallbackCrash(4)). fwRunningSlot is the slot now running.
         Sent once, after the device has a trap destination and an
         address."
    ::= { rfPowerMonitorNotifications 5 }

-- Objects

mainsPowerStatus OBJECT-TYPE
    SYNTAX      INTEGER { lost(0), present(1) }
    MAX-ACCESS  read-only
    STATUS      current
    DESCRIPTION
        "Debounced state of the mains detection input (GPIO27).
         present(1) when mains is detected, lost(0) when it is not.
         A change is reported within 10 ms; changes shorter than 5 ms
         are ignored."
    ::= { rfPowerMonitor 1 }

mainsPowerChanges OBJECT-TYPE
    SYNTAX      Counter32
    MAX-ACCESS  read-only
    STATUS      current
    DESCRIPTION
        "Number of mains state changes (loss or restore) since the
         agent started. Two changes make one outage."
    ::= { rfPowerMonitor 2 }

mainsPowerLastChange OBJECT-TYPE
    SYNTAX      TimeTicks
    MAX-ACCESS  read-only
    STATUS      current
    DESCRIPTION
        "The value of sysUpTime at the last mains state change, or 0 if
         the state has not changed since the agent started."
    ::= { rfPowerMonitor 3 }

cpuTemperature OBJECT-TYPE
    SYNTAX      Integer32 (-400..1250)
    UNITS       "0.1 degrees Celsius"
    MAX-ACCESS  read-only
    STATUS      current
    DESCRIPTION
        "Temperature of the RP2040 chip, from its on-chip sensor, in
         tenths of a degree Celsius (287 = 28.7 C), averaged over the
         last 16 seconds. This is the die temperature: it reads a few
         degrees above the air around the board and is accurate to a
         few degrees. Named boardTemperature before 2026-10-26."
    ::= { rfPowerMonitor 4 }

ambientTemperature OBJECT-TYPE
    SYNTAX      Integer32 (-400..1250)
    UNITS       "0.1 degrees Celsius"
    MAX-ACCESS  read-only
    STATUS      current
    DESCRIPTION
        "Air temperature at the carrier board, from its TMP1075 sensor
         (I2C, accurate to 1 C), in tenths of a degree Celsius
         (271 = 27.1 C), read every 2 seconds. The instance does not
         exist while the sensor does not answer (no carrier board, or
         three failed reads in a row)."
    ::= { rfPowerMonitor 5 }

mainsPowerAlarm OBJECT-TYPE
    SYNTAX      INTEGER { none(0), lostTooLong(1) }
    MAX-ACCESS  read-only
    STATUS      current
    DESCRIPTION
        "lostTooLong(1) once mainsPowerStatus has been lost(0) for 60
         seconds without a break, counted from the loss (from start-up
         if the agent started without mains); none(0) otherwise. It
         returns to none(0) when mains is restored. Alert on this rather
         than on mainsPowerStatus to ignore short outages."
    ::= { rfPowerMonitor 6 }

fwUpdate OBJECT IDENTIFIER ::= { rfPowerMonitor 7 }

fwRunningSlot OBJECT-TYPE
    SYNTAX      INTEGER { slotA(1), slotB(2) }
    MAX-ACCESS  read-only
    STATUS      current
    DESCRIPTION
        "The firmware slot the device is running. The device has two
         firmware slots; an update is written to the one that is not
         running."
    ::= { fwUpdate 1 }

fwSlotAVersion OBJECT-TYPE
    SYNTAX      DisplayString (SIZE (0..16))
    MAX-ACCESS  read-only
    STATUS      current
    DESCRIPTION
        "Firmware version in slot A, e.g. 3.4.0. Empty when the slot
         holds no valid image."
    ::= { fwUpdate 2 }

fwSlotBVersion OBJECT-TYPE
    SYNTAX      DisplayString (SIZE (0..16))
    MAX-ACCESS  read-only
    STATUS      current
    DESCRIPTION
        "Firmware version in slot B. Empty when the slot holds no valid
         image."
    ::= { fwUpdate 3 }

fwState OBJECT-TYPE
    SYNTAX      INTEGER { kept(1), trial(2) }
    MAX-ACCESS  read-only
    STATUS      current
    DESCRIPTION
        "kept(1): the running firmware is the one to keep. trial(2): the
         running firmware is new and on trial; it is kept once it has
         answered a valid management request, and the device goes back to
         the previous slot if it crashes or nobody reaches it."
    ::= { fwUpdate 4 }

fwLastResult OBJECT-TYPE
    SYNTAX      INTEGER { none(0), installed(1), rolledBackCrash(2),
                          rolledBackUnreachable(3), fallbackCrash(4) }
    MAX-ACCESS  read-only
    STATUS      current
    DESCRIPTION
        "Outcome of the last firmware update, kept across restarts.
         none(0): no update since the device was set up or reset.
         installed(1): the new firmware was kept. rolledBackCrash(2): the
         new firmware crashed during its trial. rolledBackUnreachable(3):
         the new firmware was not reached by a management request in
         time. fallbackCrash(4): the running slot crashed three times
         and the other slot took over."
    ::= { fwUpdate 5 }

-- Update site check-ins (63050.8)

updateSite OBJECT IDENTIFIER ::= { rfPowerMonitor 8 }

updCheckinResult OBJECT-TYPE
    SYNTAX      INTEGER { off(0), never(1), ok(2), failed(3) }
    MAX-ACCESS  read-only
    STATUS      current
    DESCRIPTION
        "Check-ins with the update site. off(0): no update site URL or
         no shared key, so the device does not check in. never(1): set
         up, but no check-in has succeeded yet since the device started
         or the settings changed. ok(2): the last check-in succeeded.
         failed(3): the last check-in failed (updFailedInRow says how
         many in a row)."
    ::= { updateSite 1 }

updMinutesSinceGood OBJECT-TYPE
    SYNTAX      Gauge32
    UNITS       "minutes"
    MAX-ACCESS  read-only
    STATUS      current
    DESCRIPTION
        "Minutes since the last successful check-in, or since the
         network came up when none has succeeded yet; 0 while check-ins
         are off. The device checks in every 30 minutes, so more than
         60 means check-ins are failing."
    ::= { updateSite 2 }

updFailedInRow OBJECT-TYPE
    SYNTAX      Gauge32
    MAX-ACCESS  read-only
    STATUS      current
    DESCRIPTION
        "Check-ins that failed since the last successful one."
    ::= { updateSite 3 }

-- Conformance

rfPowerMonitorConformance OBJECT IDENTIFIER ::= { rfPowerMonitor 100 }
rfPowerMonitorGroups      OBJECT IDENTIFIER ::= { rfPowerMonitorConformance 1 }
rfPowerMonitorCompliances OBJECT IDENTIFIER ::= { rfPowerMonitorConformance 2 }

rfPowerMonitorMainsGroup OBJECT-GROUP
    OBJECTS     { mainsPowerStatus, mainsPowerChanges, mainsPowerLastChange }
    STATUS      current
    DESCRIPTION
        "Mains power monitoring objects."
    ::= { rfPowerMonitorGroups 1 }

rfPowerMonitorBoardGroup OBJECT-GROUP
    OBJECTS     { cpuTemperature }
    STATUS      current
    DESCRIPTION
        "Board health objects."
    ::= { rfPowerMonitorGroups 3 }

rfPowerMonitorAmbientGroup OBJECT-GROUP
    OBJECTS     { ambientTemperature }
    STATUS      current
    DESCRIPTION
        "Ambient temperature from the carrier board's sensor."
    ::= { rfPowerMonitorGroups 4 }

rfPowerMonitorAlarmGroup OBJECT-GROUP
    OBJECTS     { mainsPowerAlarm }
    STATUS      current
    DESCRIPTION
        "Alarm for a long mains outage."
    ::= { rfPowerMonitorGroups 5 }

rfPowerMonitorAlarmNotificationGroup NOTIFICATION-GROUP
    NOTIFICATIONS { mainsPowerLostTooLong }
    STATUS      current
    DESCRIPTION
        "Notification for a long mains outage."
    ::= { rfPowerMonitorGroups 6 }

rfPowerMonitorFwGroup OBJECT-GROUP
    OBJECTS     { fwRunningSlot, fwSlotAVersion, fwSlotBVersion, fwState,
                  fwLastResult }
    STATUS      current
    DESCRIPTION
        "Firmware update state."
    ::= { rfPowerMonitorGroups 7 }

rfPowerMonitorFwNotificationGroup NOTIFICATION-GROUP
    NOTIFICATIONS { firmwareUpdateKept, firmwareRolledBack }
    STATUS      current
    DESCRIPTION
        "Firmware update notifications."
    ::= { rfPowerMonitorGroups 8 }

rfPowerMonitorUpdateSiteGroup OBJECT-GROUP
    OBJECTS     { updCheckinResult, updMinutesSinceGood, updFailedInRow }
    STATUS      current
    DESCRIPTION
        "Update site check-ins."
    ::= { rfPowerMonitorGroups 9 }

rfPowerMonitorMainsNotificationGroup NOTIFICATION-GROUP
    NOTIFICATIONS { mainsPowerLost, mainsPowerRestored }
    STATUS      current
    DESCRIPTION
        "Mains power notifications."
    ::= { rfPowerMonitorGroups 2 }

rfPowerMonitorCompliance MODULE-COMPLIANCE
    STATUS      current
    DESCRIPTION
        "Every RF-Power-Monitor agent implements all objects and
         notifications; ambientTemperature only with the sensor."
    MODULE      -- this module
        MANDATORY-GROUPS { rfPowerMonitorMainsGroup, rfPowerMonitorMainsNotificationGroup,
                           rfPowerMonitorBoardGroup, rfPowerMonitorAlarmGroup,
                           rfPowerMonitorAlarmNotificationGroup,
                           rfPowerMonitorFwGroup, rfPowerMonitorFwNotificationGroup,
                           rfPowerMonitorUpdateSiteGroup }
        GROUP       rfPowerMonitorAmbientGroup
        DESCRIPTION
            "Only on the carrier board with the TMP1075."
    ::= { rfPowerMonitorCompliances 1 }

END
