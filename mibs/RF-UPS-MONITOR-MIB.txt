RF-UPS-MONITOR-MIB DEFINITIONS ::= BEGIN

IMPORTS
    MODULE-IDENTITY, OBJECT-TYPE, NOTIFICATION-TYPE, Counter32, Integer32, TimeTicks, enterprises
        FROM SNMPv2-SMI
    MODULE-COMPLIANCE, OBJECT-GROUP, NOTIFICATION-GROUP
        FROM SNMPv2-CONF;

rfUpsMonitor MODULE-IDENTITY
    LAST-UPDATED "202611010000Z"
    ORGANIZATION "RF-UPS-Monitor project"
    CONTACT-INFO
        "https://github.com/TheKingOfChaos/RF-UPS-Monitor-v3
         kenneth@tkoc.dk"
    DESCRIPTION
        "Mains power monitor based on a Raspberry Pi Pico with a W5500
         Ethernet module. The agent speaks SNMPv1 only and all objects
         are read-only. The standard system group (RFC 1213) is also
         implemented."
    REVISION "202611010000Z"
    DESCRIPTION
        "Added mainsPowerAlarm and the mainsPowerLostTooLong notification
         (SNMPv1 specific-trap 3): mains lost for 60 seconds."
    REVISION "202610260000Z"
    DESCRIPTION
        "boardTemperature renamed cpuTemperature (same OID, same value).
         Added ambientTemperature from the TMP1075 on the carrier board."
    REVISION "202610170100Z"
    DESCRIPTION
        "Added boardTemperature (firmware 1.0.0)."
    REVISION "202610170000Z"
    DESCRIPTION
        "Added mainsPowerLost and mainsPowerRestored notifications,
         sent as SNMPv1 traps (enterprise 63050, specific-trap 1 and 2)."
    REVISION "202610160000Z"
    DESCRIPTION
        "Initial version: mains power status, change counter and time
         of the last change."
    ::= { enterprises 63050 }

-- Notifications. Under RFC 3584 these map to SNMPv1 traps with
-- enterprise = rfUpsMonitor and specific-trap = the last sub-identifier.

rfUpsMonitorNotifications OBJECT IDENTIFIER ::= { rfUpsMonitor 0 }

mainsPowerLost NOTIFICATION-TYPE
    OBJECTS     { mainsPowerStatus, mainsPowerChanges, mainsPowerLastChange }
    STATUS      current
    DESCRIPTION
        "Mains power was lost. mainsPowerLastChange is the time of the
         loss; the trap time-stamp has the same value."
    ::= { rfUpsMonitorNotifications 1 }

mainsPowerRestored NOTIFICATION-TYPE
    OBJECTS     { mainsPowerStatus, mainsPowerChanges, mainsPowerLastChange }
    STATUS      current
    DESCRIPTION
        "Mains power was restored."
    ::= { rfUpsMonitorNotifications 2 }

mainsPowerLostTooLong NOTIFICATION-TYPE
    OBJECTS     { mainsPowerStatus, mainsPowerChanges, mainsPowerLastChange,
                  mainsPowerAlarm }
    STATUS      current
    DESCRIPTION
        "Mains power has been lost for 60 seconds: mainsPowerAlarm became
         lostTooLong(1). Sent once per outage; if no trap destination
         exists at that moment, it is sent as soon as one does, unless
         mains returns first. mainsPowerLastChange and the trap
         time-stamp are the time of the loss."
    ::= { rfUpsMonitorNotifications 3 }

-- Objects

mainsPowerStatus OBJECT-TYPE
    SYNTAX      INTEGER { lost(0), present(1) }
    MAX-ACCESS  read-only
    STATUS      current
    DESCRIPTION
        "Debounced state of the mains detection input (GPIO27).
         present(1) when mains is detected, lost(0) when it is not.
         A change is reported within 10 ms; changes shorter than 5 ms
         are ignored."
    ::= { rfUpsMonitor 1 }

mainsPowerChanges OBJECT-TYPE
    SYNTAX      Counter32
    MAX-ACCESS  read-only
    STATUS      current
    DESCRIPTION
        "Number of mains state changes (loss or restore) since the
         agent started. Two changes make one outage."
    ::= { rfUpsMonitor 2 }

mainsPowerLastChange OBJECT-TYPE
    SYNTAX      TimeTicks
    MAX-ACCESS  read-only
    STATUS      current
    DESCRIPTION
        "The value of sysUpTime at the last mains state change, or 0 if
         the state has not changed since the agent started."
    ::= { rfUpsMonitor 3 }

cpuTemperature OBJECT-TYPE
    SYNTAX      Integer32 (-400..1250)
    UNITS       "0.1 degrees Celsius"
    MAX-ACCESS  read-only
    STATUS      current
    DESCRIPTION
        "Temperature of the RP2040 chip, from its on-chip sensor, in
         tenths of a degree Celsius (287 = 28.7 C), averaged over the
         last 16 seconds. This is the die temperature: it reads a few
         degrees above the air around the board and is accurate to a
         few degrees. Named boardTemperature before 2026-10-26."
    ::= { rfUpsMonitor 4 }

ambientTemperature OBJECT-TYPE
    SYNTAX      Integer32 (-400..1250)
    UNITS       "0.1 degrees Celsius"
    MAX-ACCESS  read-only
    STATUS      current
    DESCRIPTION
        "Air temperature at the carrier board, from its TMP1075 sensor
         (I2C, accurate to 1 C), in tenths of a degree Celsius
         (271 = 27.1 C), read every 2 seconds. The instance does not
         exist while the sensor does not answer (no carrier board, or
         three failed reads in a row)."
    ::= { rfUpsMonitor 5 }

mainsPowerAlarm OBJECT-TYPE
    SYNTAX      INTEGER { none(0), lostTooLong(1) }
    MAX-ACCESS  read-only
    STATUS      current
    DESCRIPTION
        "lostTooLong(1) once mainsPowerStatus has been lost(0) for 60
         seconds without a break, counted from the loss (from start-up
         if the agent started without mains); none(0) otherwise. It
         returns to none(0) when mains is restored. Alert on this rather
         than on mainsPowerStatus to ignore short outages."
    ::= { rfUpsMonitor 6 }

-- Conformance

rfUpsMonitorConformance OBJECT IDENTIFIER ::= { rfUpsMonitor 100 }
rfUpsMonitorGroups      OBJECT IDENTIFIER ::= { rfUpsMonitorConformance 1 }
rfUpsMonitorCompliances OBJECT IDENTIFIER ::= { rfUpsMonitorConformance 2 }

rfUpsMonitorMainsGroup OBJECT-GROUP
    OBJECTS     { mainsPowerStatus, mainsPowerChanges, mainsPowerLastChange }
    STATUS      current
    DESCRIPTION
        "Mains power monitoring objects."
    ::= { rfUpsMonitorGroups 1 }

rfUpsMonitorBoardGroup OBJECT-GROUP
    OBJECTS     { cpuTemperature }
    STATUS      current
    DESCRIPTION
        "Board health objects."
    ::= { rfUpsMonitorGroups 3 }

rfUpsMonitorAmbientGroup OBJECT-GROUP
    OBJECTS     { ambientTemperature }
    STATUS      current
    DESCRIPTION
        "Ambient temperature from the carrier board's sensor."
    ::= { rfUpsMonitorGroups 4 }

rfUpsMonitorAlarmGroup OBJECT-GROUP
    OBJECTS     { mainsPowerAlarm }
    STATUS      current
    DESCRIPTION
        "Alarm for a long mains outage."
    ::= { rfUpsMonitorGroups 5 }

rfUpsMonitorAlarmNotificationGroup NOTIFICATION-GROUP
    NOTIFICATIONS { mainsPowerLostTooLong }
    STATUS      current
    DESCRIPTION
        "Notification for a long mains outage."
    ::= { rfUpsMonitorGroups 6 }

rfUpsMonitorMainsNotificationGroup NOTIFICATION-GROUP
    NOTIFICATIONS { mainsPowerLost, mainsPowerRestored }
    STATUS      current
    DESCRIPTION
        "Mains power notifications."
    ::= { rfUpsMonitorGroups 2 }

rfUpsMonitorCompliance MODULE-COMPLIANCE
    STATUS      current
    DESCRIPTION
        "Every RF-UPS-Monitor agent implements all objects and
         notifications; ambientTemperature only with the sensor."
    MODULE      -- this module
        MANDATORY-GROUPS { rfUpsMonitorMainsGroup, rfUpsMonitorMainsNotificationGroup,
                           rfUpsMonitorBoardGroup, rfUpsMonitorAlarmGroup,
                           rfUpsMonitorAlarmNotificationGroup }
        GROUP       rfUpsMonitorAmbientGroup
        DESCRIPTION
            "Only on the carrier board with the TMP1075."
    ::= { rfUpsMonitorCompliances 1 }

END
